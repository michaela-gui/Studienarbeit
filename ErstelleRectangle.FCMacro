FreeCADGui.Gui.runCommand('Std_Workbench',18)
Gui.runCommand('Std_ViewStatusBar',1)
Gui.runCommand('Std_DlgMacroExecute',0)
myrect = Draft.makeRectangle(4, 3)
import Draft
myrect = Draft.makeRectangle(4, 3)
App.setActiveDocument("TestPythonSkripting")
doc = FreeCAD.openDocument('C:/Users/mfle/AppData/Roaming/FreeCAD/Macro/TestPythonSkripting.FCStd')
# App.setActiveDocument("TestPythonSkripting")
# App.ActiveDocument=App.getDocument("TestPythonSkripting")
# Gui.ActiveDocument=Gui.getDocument("TestPythonSkripting")
Gui.runCommand('Std_OrthographicCamera',1)
App.setActiveDocument("TestPythonSkripting")
myrect = Draft.makeRectangle(4, 3)
mydistance = FreeCAD.Vector(2,5,0)
mydistance = FreeCAD.Vector(2,5,0)
Draft.move(myrect, mydistance)
mydistance = FreeCAD.Vector(5,5,5)
Draft.move(myrect, mydistance)
# Gui.Selection.clearSelection()
# Gui.Selection.addSelection('TestPythonSkripting','myBoy','Face6',9.72954,8.66264,5)
# Gui.Selection.clearSelection()
# Gui.Selection.addSelection('TestPythonSkripting','myBoy','Face4',10.5544,9,3.43059)
# Gui.Selection.clearSelection()
# Gui.Selection.addSelection('TestPythonSkripting','Rectangle')
# Gui.Selection.clearSelection()
# Gui.Selection.addSelection('TestPythonSkripting','Rectangle001')
# Gui.Selection.clearSelection()
# Gui.Selection.addSelection('TestPythonSkripting','Rectangle')
mydistance = FreeCAD.Vector(10,10,10)
Draft.move(myrect, mydistance)
# Gui.Selection.clearSelection()
# Gui.Selection.addSelection('TestPythonSkripting','MyShape')
# Gui.Selection.clearSelection()
# Gui.Selection.addSelection('TestPythonSkripting','Shape')
# Gui.Selection.clearSelection()
# Gui.Selection.addSelection('TestPythonSkripting','myBoy')
# Gui.Selection.clearSelection()
# Gui.Selection.addSelection('TestPythonSkripting','myBoy')
# Gui.Selection.clearSelection()
# Gui.Selection.addSelection('TestPythonSkripting','Rectangle')
# Gui.Selection.clearSelection()
# Gui.Selection.addSelection('TestPythonSkripting','MyShape','Face1',-0.41746,5.568,8.2832)
# Gui.Selection.clearSelection()
### Begin command Std_ViewIsometric
Gui.activeDocument().activeView().viewIsometric()
### End command Std_ViewIsometric
### Begin command Std_Part
App.activeDocument().Tip = App.activeDocument().addObject('App::Part','Part')
App.activeDocument().Part.Label = 'Part'
Gui.activateView('Gui::View3DInventor', True)
Gui.activeView().setActiveObject('part', App.activeDocument().Part)
App.ActiveDocument.recompute()
### End command Std_Part
# Gui.Selection.addSelection('TestPythonSkripting','Rectangle001','Face1',19.2769,20.4964,15)
# Gui.Selection.clearSelection()
# Gui.Selection.addSelection('TestPythonSkripting','Rectangle','Edge2',9,5.16176,0)
Gui.runCommand('Std_Open',0)
### Begin command Std_New
App.newDocument("Unbenannt")
# App.setActiveDocument("Unbenannt")
# App.ActiveDocument=App.getDocument("Unbenannt")
# Gui.ActiveDocument=Gui.getDocument("Unbenannt")
Gui.activeDocument().activeView().viewDefaultOrientation()
### End command Std_New
# Gui.Selection.clearSelection()
### Begin command Std_Part
App.activeDocument().Tip = App.activeDocument().addObject('App::Part','Part')
App.activeDocument().Part.Label = 'Part'
Gui.activateView('Gui::View3DInventor', True)
Gui.activeView().setActiveObject('part', App.activeDocument().Part)
App.ActiveDocument.recompute()
### End command Std_Part
# Gui.Selection.addSelection('Unbenannt','Part')
# Gui.Selection.clearSelection()
# Gui.Selection.addSelection('Unbenannt','Part','Origin.')
myrect = Draft.makeRectangle(4,3)
mydistance = FreeCAD.Vector(0,2,1)
Draft.move(myrect, mydistance)
Gui.reload
Gui.reload()
Gui.reload(1)
Gui.reload("Rectangle")
# Gui.Selection.clearSelection()
# Gui.Selection.addSelection('Unbenannt','Rectangle')
# Gui.Selection.clearSelection()
